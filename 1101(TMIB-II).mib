--******************************************************************************
-- Filename:    1101(TMIB-II).MIB
-- Source:      NTCIP 1101:1996
--              NEMA TS 3.2-1996 Amendment 1
-- Description: This MIB defines the structure of information under the nema
--              transportation node
-- MIB Revision History:
-- 01/01/98     Preliminary Release of TS 3.2 TMIB MIB formatted for 80
--              columns and no TABs
-- 01/07/98     Replaced some missed TABs with spaces
-- 07/08/98     Added Copyright Notice
-- 03/09/00	    Removed all the special edits to that were done to use the 
--              SMIC Compiler
--              Defined DisplayString to eliminate need to compile RFC 1212
--              END is still left "Dynamic Object Data" group
--              Changed filename and updated copyright years
--              Updated the MIB to Amendment 1
-- 08/09/00     Modified header format and wording of copyright and MIB
--              Distribution Notice
--
--Copyright 1996-2000 by the American Association of State Highway and
--Transportation Officials (AASHTO), the Institute of Transportation Engineers
--(ITE), and the National Electrical Manufacturers Association (NEMA).  All
--intellectual property rights, including, but not limited to, the rights of
--reproduction in whole or in part in any form, translation into other
--languages and display are reserved by the copyright owners under the laws of
--the United States of America, the Universal Copyright Convention, the Berne
--Convention, and the International and Pan American Copyright Conventions.
--Except for the MIB, Do not copy without written permission of either AASHTO,
--ITE, or NEMA.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned 
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS.  AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES.  Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--******************************************************************************


TMIB-II DEFINITIONS ::= BEGIN
--
-- Initial MIB for Standard Transportation Management Framework
-- structure of management information (STMF).
--
IMPORTS
--      ObjectName
--              FROM RFC1155-SMI
--       DisplayString
--                FROM RFC1158-MIB
        OBJECT-TYPE
                FROM RFC-1212
-- NEMA has received ID 1206 from IANA
    transportation
    FROM NEMA_SMI;


--EXPORTS -- EVERYTHING
-- Major groups of the TMIB.
--  protocols, dynObjMgmt, dynObjDef, dynObjData, profiles, devices
--  dynObjEntry, dynObjNumber, dynObjIndex, dynObjVariable, dynObjOwner,
--  dynObjStatus, dynObj1, dynObj2, dynObj3, dynObj4, dynObj5, dynObj6, 
--  dynObj7, dynObj8, dynObj9, dynObj10, dynObj11, dynObj12, dynObj13;

--This MIB module uses the extended OBJECT-TYPE macro as
-- defined in RFC-1212;

DisplayString ::=
              OCTET STRING


---- *****************************************************************
----            Special Object Type Definitions
---- *****************************************************************


-- The following are subtypes of conventional types formed by
-- subtyping ASN types.


Byte ::=        INTEGER (-128..127)
UByte ::=       INTEGER (0..255)

Short ::=       INTEGER (-32768..32767)
UShort ::=      INTEGER (0..65535)

Long ::=        INTEGER (-2147483648..2147483647)
ULong ::=       INTEGER (0..4294967295)


ConfigEntryStatus  ::= INTEGER
   { valid (1),
     underCreation (2),
     invalid (3)
   }
   -- See Section 4.1.2 for complete definition of this Type. It replaces the 
   -- following that is now deprecated

EntryStatus  ::= INTEGER
	{ valid (1),
	  underCreation (2),
	  invalid (3)
	}
-- See Section 4.1.4 for a complete definition of this Type.

OwnerString ::= DisplayString (SIZE(0..127))
-- This data type is used to model an administratively assigned name of the
-- owner of a resource.  This information is taken from the NVT ASCII character
-- set.  It is suggested that this name contain one or more of the following:
-- management station name, manager's name, location or phone number.
-- 
-- SNMP access control is articulated entirely in terms of the contents of MIB
-- views; access to a particular SNMP object instance depends only upon its
-- presence or absence in a particular MIB view and never upon its value or the
-- value of related object instances.  Thus, objects of this type afford
-- resolution of resource contention only among cooperating managers; they
-- realize no access control function with respect to uncooperative parties.
--
-- By convention, objects with this syntax are declared as having
--
--      SIZE ( 0..127 )


-- *****************************************************************
--              GROUPS WITHIN THE TMIB
-- *****************************************************************
-- *****************************************************************
--              Protocol Group
-- *****************************************************************
-- The protocols group contains information about specific implementations
-- of different protocols.
--
protocols       OBJECT IDENTIFIER ::= { transportation 1 }

layers          OBJECT IDENTIFIER ::= { protocols 1 }
                  
profiles        OBJECT IDENTIFIER ::= { protocols 2 }

dynObjMgmt      OBJECT IDENTIFIER ::= { protocols 3 }

   dynObjData      OBJECT IDENTIFIER ::= { dynObjMgmt 2 }

--********************************************************************
--              Device Group
--********************************************************************
devices         OBJECT IDENTIFIER ::= { transportation 2 }



--*********************************************************************
--              Dynamic Object Group
-- ********************************************************************


dynObjDef  OBJECT-TYPE
   SYNTAX  SEQUENCE OF DynObjEntry
   ACCESS  not-accessible
   STATUS  mandatory
   DESCRIPTION
      "A list of objects to be included in dynamic objects"
::= { dynObjMgmt 1 }

dynObjEntry  OBJECT-TYPE
   SYNTAX  DynObjEntry
   ACCESS  not-accessible
   STATUS  mandatory
   DESCRIPTION
      "A list of OBJECT IDENTIFIERs that make up a dynamic object"
   INDEX  { dynObjNumber,  dynObjIndex }
::= { dynObjDef 1 }

DynObjEntry ::= SEQUENCE {
   dynObjNumber    INTEGER (1..13),
   dynObjIndex     INTEGER (1..255),
   dynObjVariable  OBJECT IDENTIFIER,
   dynObjOwner     OwnerString,
   dynObjStatus    EntryStatus  }

dynObjNumber  OBJECT-TYPE
   SYNTAX  INTEGER ( 1..13)
   ACCESS  read-only
   STATUS  mandatory
   DESCRIPTION
      "The dynamic object number that this entry is to be associated with."
::= { dynObjEntry 1 }

dynObjIndex  OBJECT-TYPE
   SYNTAX  INTEGER (1..255)
   ACCESS  read-only
   STATUS  mandatory
   DESCRIPTION
      "An index that uniquely identifies an entry in the dynamic object table. Each
	  entry defines an object that is to be associated with a dynamic object number.
	  The dynObjIndex determines the  order in which objects are transmitted
	  for the dynamic object.  The lower dynObjIndex numbers
	  are transmitted before larger numbers for entries within the same dynamic object."
::= { dynObjEntry 2 }

dynObjVariable OBJECT-TYPE
   SYNTAX  OBJECT IDENTIFIER
   ACCESS  read-write
   STATUS  mandatory
   DESCRIPTION
      "The object identifier of the particular variable to be included in the
	  specified dynamic object number.  Care must be taken when defining 
	  dynamic objects that the maximum size of all the objects included in a 
	  dynamic object do not exceed the maximum packet size of the 
	  communications network.
   
      When set to reference a columnar object, an agent may wish to only
	  validate the prefix portion of the object identifier.  The suffix or index
	  portion of an object identifier need not be instantiated or exist at the time
	  the time a dynObjVariable is defined.

      This object may not be modified unless the associated dynObjStatus object is
	  equal to underCreation."
::= { dynObjEntry 3 }

dynObjOwner OBJECT-TYPE
   SYNTAX  OwnerString
   ACCESS  read-write
   STATUS  deprecated
   DESCRIPTION
      "This object has been replaced with dynObjConfigOwner.
      
      The entity that configured this entry and is therefore using the 
      resources assigned to it.
      This object may not be modified if the associated dynObjStatus object is
	  equal to valid(1).
	  
	  This object has been replaced with dynObjConfigOwner."
::= { dynObjEntry 4 }

dynObjStatus OBJECT-TYPE
   SYNTAX  EntryStatus
   ACCESS  read-write
   STATUS  deprecated
   DESCRIPTION
      "This object has been replaced with dynObjConfigOwner.
      
      The status of this dynamic object definition entry.  See description of 
      EntryStatus above for restrictions on accesses

	  This object has been replaced with dynObjConfigStatus."
::= { dynObjEntry 5 }


--***********************************************************************
--              Dynamic Object Data
-- all objects under this node have been depricateddue to their limited
-- usefulness.
--***********************************************************************
-- ALL OBJECTS UNDER THIS NODE HAVE BEEN DEPRECATED
-- DUE TO THEIR LIMITED USEFULNESS

dynObj1  OBJECT-TYPE
   SYNTAX  OCTET STRING
   ACCESS  read-write
   STATUS  deprecated
   DESCRIPTION
      "The value of this object is determined by the dynObjDef entries with 
      dynObjNumber equal to 1.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 1 }

dynObj2  OBJECT-TYPE
   SYNTAX  OCTET STRING
   ACCESS  read-write
   STATUS  deprecated
   DESCRIPTION
      "The value of this object is determined by the dynObjDef entries with 
      dynObjNumber equal to 2.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 2 }

dynObj3  OBJECT-TYPE
   SYNTAX  OCTET STRING
   ACCESS  read-write
   STATUS  deprecated
   DESCRIPTION
      "The value of this object is determined by the dynObjDef entries with 
      dynObjNumber equal to 3.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 3 }

dynObj4  OBJECT-TYPE
   SYNTAX  OCTET STRING
   ACCESS  read-write
   STATUS  deprecated
   DESCRIPTION
      "The value of this object is determined by the dynObjDef entries with 
      dynObjNumber equal to 4.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 4 }

dynObj5  OBJECT-TYPE
   SYNTAX  OCTET STRING
   ACCESS  read-write
   STATUS  deprecated
   DESCRIPTION
      "The value of this object is determined by the dynObjDef entries with 
      dynObjNumber equal to 5.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 5 }

dynObj6  OBJECT-TYPE
   SYNTAX  OCTET STRING
   ACCESS  read-write
   STATUS  deprecated
   DESCRIPTION
      "The value of this object is determined by the dynObjDef entries with 
      dynObjNumber equal to 6.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 6 }

dynObj7  OBJECT-TYPE
   SYNTAX  OCTET STRING
   ACCESS  read-write
   STATUS  deprecated
   DESCRIPTION
      "The value of this object is determined by the dynObjDef entries with 
      dynObjNumber equal to 7.  Packed Encoding Rules are utilized to encode
      the objects for transmission.  This object is intended for use with the 
      Simple Transportation Management Protocol, and provides little advantage 
      if used with SNMP.
      If no objects are defined for this dynamic object number, then an error of 
      noSuchName shall be returned by the agent"
::= { dynObjData 7 }

dynObj8  OBJECT-TYPE
   SYNTAX  OCTET STRING
   ACCESS  read-write
   STATUS  deprecated
   DESCRIPTION
      "The value of this object is determined by the dynObjDef entries with 
      dynObjNumber equal to 8.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 8 }

dynObj9  OBJECT-TYPE
   SYNTAX  OCTET STRING
   ACCESS  read-write
   STATUS  deprecated
   DESCRIPTION
      "The value of this object is determined by the dynObjDef entries with 
      dynObjNumber equal to 9.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 9 }

dynObj10  OBJECT-TYPE
   SYNTAX  OCTET STRING
   ACCESS  read-write
   STATUS  deprecated
   DESCRIPTION
      "The value of this object is determined by the dynObjDef entries with 
      dynObjNumber equal to 10.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 10 }

dynObj11  OBJECT-TYPE
   SYNTAX  OCTET STRING
   ACCESS  read-write
   STATUS  deprecated
   DESCRIPTION
      "The value of this object is determined by the dynObjDef entries with 
      dynObjNumber equal to 11.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 11 }

dynObj12  OBJECT-TYPE
   SYNTAX  OCTET STRING
   ACCESS  read-write
   STATUS  deprecated
   DESCRIPTION
      "The value of this object is determined by the dynObjDef entries with 
      dynObjNumber equal to 12.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 12 }

dynObj13  OBJECT-TYPE
        SYNTAX  OCTET STRING
   ACCESS  read-write
   STATUS  deprecated
   DESCRIPTION
    "The value of this object is determined by the dynObjDef entries with 
      dynObjNumber equal to 13.  Packed Encoding Rules are utilized to encode
      the objects for transmission.  This object is intended for use with the 
	  Simple Transportation Management Protocol, and provides little advantage 
	  if used with SNMP.
      If no objects are defined for this dynamic object number, then an error of 
      noSuchName shall be returned by the agent"
::= { dynObjData 13 }

--*********************************************************************
-- 		Dynamic Object Configuration Group
-- ********************************************************************

dynObjConfig OBJECT IDENTIFIER ::= { dynObjMgmt 3}

dynObjConfigTable  OBJECT-TYPE
	SYNTAX  SEQUENCE OF DynObjConfigEntry
	ACCESS  not-accessible
	STATUS  mandatory
	DESCRIPTION
		"A table consisting of an owner and status for each of the 13 dynamic object definitions."
::= { dynObjConfig 1 }

dynObjConfigEntry  OBJECT-TYPE
	SYNTAX  DynObjConfigEntry
	ACCESS  not-accessible
	STATUS  mandatory
	DESCRIPTION
		"A table consisting of an owner and status for each of the 13 dynamic object definitions."
	INDEX  { dynObjNumber }
::= { dynObjConfigTable  1 }

DynObjConfigEntry ::= SEQUENCE {
	dynObjConfigOwner	OwnerString,
	dynObjConfigStatus	ConfigEntryStatus  }

dynObjConfigOwner OBJECT-TYPE
	SYNTAX  OwnerString
	ACCESS  read-write
	STATUS  mandatory
	DESCRIPTION
		"The entity that configured the associated dynamic object."
::= { dynObjConfigEntry 1 }


dynObjConfigStatus OBJECT-TYPE
	SYNTAX  ConfigEntryStatus
	ACCESS  read-write
	STATUS  mandatory
	DESCRIPTION
         "Indicates the state of the associated dynamic object.  Depending on the validity checks that are
          performed on the dynamic object definition, a set request may or may not be honored.   See
          Section 4.1.4 for a complete description."
::= { dynObjConfigEntry 2 }

END -- TMIB-II DEFINITIONS
