-- A.1 SMI HEADER
--****************************************************************************
-- Filename:    8004v0217MIB
-- Source:      NTCIP 8004 v02.17
-- Description: This MIB defines the overall structure of the 
--              NTCIP-defined management information and several textual 
--              conventions that are believed to be useful for a broad range 
--              of applications
-- MIB Revision History:
-- 10/01/96     NEMA TS 3.2 approved
-- 01/01/98     Preliminary Release of TS 3.2 NEMA_SMI MIB formatted for
--              80 columns and no tabs
-- 07/08/98     Added Copyright Notice
-- 10/08/98     Amendment 1 approved
-- 03/09/00     Changed filename and updated copyright years
--              Updated the MIB to Amendment  
-- 08/09/00     Modified header format and wording of copyright and MIB
--              Distribution Notice
-- 11/16/01     Incorporated into NTCIP 1103, defined tree down to and
--              including device nodes, and changed filename
-- 9/19/02      Incorporated into NTCIP 8004 and changed filename and module
--              name
-- 09/27/04     Updated header information and END remark
-- 01/26/05     Added chap and modem to list of Object Identifier nodes.
-- 02/12/05     Removed embedded comment indicator between EXPORTS and
--              EVERYTHING
-- 11/29/07     Added tmdd and ntcipTraps nodes
-- 03/16/10     Edited Jointly Approved NTCIP 8004 v02 for publication.
-- 
--Copyright 2010 by the American Association of State Highway and
--Transportation Officials (AASHTO), the Institute of Transportation
--Engineers (ITE), and the National Electrical Manufacturers Association
--(NEMA). All intellectual property rights, including, but not limited to,
--the rights of reproduction in whole or in part in any form, translation
--into other languages and display are reserved by the copyright owners under
--the laws of the United States of America, the Universal Copyright
--Convention, the Berne Convention, and the International and Pan American
--Copyright Conventions. Except for the MIB, Do not copy without written 
--permission of either AASHTO,ITE, or NEMA.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:

--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned 
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their
--use or performance.
--
--AASHTO/ITE/NEMA AND THEIR SUPPLIERS DO NOT WARRANT THE PERFORMANCE OR
--RESULTS YOU MAY OBTAIN BY USING THESE MATERIALS. AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR
--NEMA REPRESENTATIVE HAS BEEN ADVISED OF THE POSSIBILITY OF SUCH DAMAGES.
--Some states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--**************************************************************************

NTCIP8004v02 DEFINITIONS ::= BEGIN

-- Initial definitions for Structure of Management Information.
-- This contains only structure information, no managed objects are defined

IMPORTS
   DisplayString
       FROM RFC1213-MIB
   enterprises
       FROM RFC1155-SMI;

-- EXPORTS EVERYTHING

-- A.2 STRUCTURE INFORMATION 
nema                    OBJECT IDENTIFIER  ::=  { enterprises 1206 }
-- NEMA has received ID 1206 from IANA
-- NEMA starts at { iso org dod internet private enterprises 1206 } in the 
-- global naming tree.

nemaMgmt                OBJECT IDENTIFIER  ::=  { nema 1 }
-- The mgmt subtree is used for standard NEMA object definitions that span 
-- different NEMA sections.

nemaExperimental        OBJECT IDENTIFIER  ::=  { nema 2 }
-- The experimental subtree is used for technical committees developing 
-- objects that may become standard in the future.

nemaPrivate             OBJECT IDENTIFIER  ::=  { nema 3 }
-- The private subtree is used for unilaterally defined objects. One common 
-- use is for manufacturer-specific or customer-specific MIB definitions.

transportation          OBJECT IDENTIFIER  ::=  { nema 4 }
-- The transportation subtree is used by the NTCIP to define
-- standard objects specific for the transportation industry.

protocols         OBJECT IDENTIFIER  ::=  { transportation 1 }
devices           OBJECT IDENTIFIER  ::=  { transportation 2 }
tcip              OBJECT IDENTIFIER  ::=  { transportation 3 }
tmdd              OBJECT IDENTIFIER  ::=  { transportation 4 }
layers            OBJECT IDENTIFIER  ::=  { protocols 1 }
application       OBJECT IDENTIFIER  ::=  { layers 7 }
profiles          OBJECT IDENTIFIER  ::=  { protocols 2 }
dynObjMgmt        OBJECT IDENTIFIER  ::=  { protocols 3 }
ntcipTraps        OBJECT IDENTIFIER  ::=  { protocols 4 }

asc               OBJECT IDENTIFIER  ::=  { devices 1 }
ramp              OBJECT IDENTIFIER  ::=  { devices 2 }
dms               OBJECT IDENTIFIER  ::=  { devices 3 }
tss               OBJECT IDENTIFIER  ::=  { devices 4 }
ess               OBJECT IDENTIFIER  ::=  { devices 5 }
global            OBJECT IDENTIFIER  ::=  { devices 6 }
cctv              OBJECT IDENTIFIER  ::=  { devices 7 }
cctvSwitch        OBJECT IDENTIFIER  ::=  { devices 8 }
dcm               OBJECT IDENTIFIER  ::=  { devices 9 }
ssm               OBJECT IDENTIFIER  ::=  { devices 10 }
scp               OBJECT IDENTIFIER  ::=  { devices 11 }
networkCamera     OBJECT IDENTIFIER  ::=  { devices 12 }
elms              OBJECT IDENTIFIER  ::=  { devices 13 }

chap              OBJECT IDENTIFIER  ::=  {layers 1}
modem             OBJECT IDENTIFIER  ::=  {layers 2}

-- A.3 COMMON TEXTUAL CONVENTIONS
OerString ::= OCTET STRING

Byte      ::= INTEGER (-128..127)
Ubyte     ::= INTEGER (0..255)
Short     ::= INTEGER (-32768..32767)
Ushort    ::= INTEGER (0..65535)
Long      ::= INTEGER (-2147483648..2147483647)

BITMAP8   ::= OCTET STRING (SIZE (1))
BITMAP16  ::= OCTET STRING (SIZE (2))
BITMAP32  ::= OCTET STRING (SIZE (4))

OwnerString	::= DisplayString (SIZE (0..127))
-- This data type is used to model an administratively assigned name of the 
-- owner of a resource. This information is taken from the NVT ASCII 
-- character set. It is suggested that this name contain one or more of the 
-- following: management station name, manager’s name, location or phone 
-- number.
-- 
-- SNMP access control is articulated entirely in terms of the contents of 
-- MIB views; access to a particular SNMP object instance depends only upon 
-- its presence or absence in a particular MIB view and never upon its value 
-- or the value of related object instances. Thus, objects of this type 
-- afford resolution of resource contention only among cooperating managers; 
-- they realize no access control function with respect to uncooperative 
-- parties.
--
-- Objects with this syntax are declared as having
--     SIZE ( 0..127 )

RowStatusStatic  ::= INTEGER
                   { other (1),
                     standby (2),
                     available (3),
                     invalid (4), 
                     activate (5),
                     deactivate (6)}

END -- NTCIP8004v02 Definitions
