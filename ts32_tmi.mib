--******************************************************************************
-- Filename:    TS32_TMI.MIB
-- Version:     0.A
-- Date:        January 1, 1998
-- Description: This MIB defines the structure of information under the nema
--              transportation node
-- Revision:    A - Preliminary Release of TS 3.2 TMIB MIB formatted for 80
--              columns and no TABs
-- SMIC Compiler
-- Notes:
--              Commented IMPORTS of ObjectName, DisplayString, and OBJECT-TYPE
--              Added SMI OBJECT-TYPE
--              Dropped EXPORTS
--              Moved END to before "Dynamic Object Data" group
--              Changed DISPLAY STRING TO OCTET STRING
--
--******************************************************************************


TMIB DEFINITIONS ::= BEGIN
--
-- Initial MIB for Standard Transportation Management Framework
-- structure of management information (STMF).
--
IMPORTS
    transportation
    FROM NEMA_SMI;
--      ObjectName
--              FROM RFC1155-SMI;
--       DisplayString
--                FROM RFC1158-MIB
--        OBJECT-TYPE
--                FROM RFC1212
-- NEMA has received ID 1206 from IANA
SMI OBJECT-TYPE

--EXPORTS -- EVERYTHING
-- Major groups of the TMIB.
--  protocols, dynObjMgmt, dynObjDef, dynObjData, profiles, devices
--  dynObjEntry, dynObjNumber, dynObjIndex, dynObjVariable, dynObjOwner,
--  dynObjStatus, dynObj1, dynObj2, dynObj3, dynObj4, dynObj5, dynObj6, 
--  dynObj7, dynObj8, dynObj9, dynObj10, dynObj11, dynObj12, dynObj13;

--This MIB module uses the extended OBJECT-TYPE macro as
-- defined in RFC-1212;


---- *****************************************************************
----            Special Object Type Definitions
---- *****************************************************************


-- The following are subtypes of conventional types formed by
-- subtyping ASN types.


Byte ::=        INTEGER (-127..127)
UByte ::=       INTEGER (0..255)

Short ::=       INTEGER (-32782..32782)
UShort ::=      INTEGER (0..65535)

Long ::=        INTEGER (-2147483647..2147483647)
ULong ::=       INTEGER (0..4294967295)


EntryStatus  ::= INTEGER
   { valid (1),
     createRequest (2),
     underCreation (3),
     invalid (4)
   }

-- The EntryStatus shows the status of a table entry
-- Setting this object to the value invalid(4) has the effect of invalidating
-- the corresponding entry.  That is, it effectively disassociates the mapping 
-- identified with said entry.
-- It is an implementation specific matter as to whether the agent removes
-- an invalidated entry from the table.  Accordingly managers must be 
-- prepared to receive tabular information from agents that corresponds to 
-- entries currently not in use.  Proper interpretation of such entries
-- requires examination of the relevant EntryStatus object.
--
-- An existing instance of this object cannot be set to createRequest(2).  This
-- object may only be set to createRequest(2) when the instance is created.
-- When this object is created, the agent may wish to create supplemental object
-- instances to complete a conceptual row in this table.  Immediately after 
-- completing the create operation, the agent must set this object to
-- underCreation(3).
--
-- Entries shall exist in the underCreation(3) state until the management
-- station is finished configuring the entry and sets this object to valid(1) or
-- aborts, and sets this object to invalid(4).  If the agent determines that an
-- entry has been in the underCreation(3) state fro an abnormally long time, it
-- may decide that the management station has crashed.  If the agent makes this
-- decision, it may set this object to invalid(4) to reclaim the entry.  A
-- prudent agent will understand that the management station may need to wait
-- for human input and will allow for that possibility in its determination of
-- this abnormally long period.


OwnerString ::= OCTET STRING (SIZE(0..127))
-- This data type is used to model an administratively assigned name of the
-- owner of a resource.  This information is taken from the NVT ASCII character
-- set.  It is suggested that this name contain one or more of the following:
-- management station name, manager's name, location or phone number.
-- 
-- SNMP access control is articulated entirely in terms of the contents of MIB
-- views; access to a particular SNMP object instance depends only upon its
-- presence or absence in a particular MIB view and never upon its value or the
-- value of related object instances.  Thus, objects of this type afford
-- resolution of resource contention only among cooperating managers; they
-- realize no access control function with respect to uncooperative parties.
--
-- By convention, objects with this syntax are declared as having
--
--      SIZE ( 0..127 )


-- *****************************************************************
--              GROUPS WITHIN THE TMIB
-- *****************************************************************
-- *****************************************************************
--              Protocol Group
-- *****************************************************************
-- The protocols group contains information about specific implementations
-- of different protocols.
--
protocols       OBJECT IDENTIFIER ::= { transportation 1 }

layers          OBJECT IDENTIFIER ::= { protocols 1 }
                  
profiles        OBJECT IDENTIFIER ::= { protocols 2 }

dynObjMgmt      OBJECT IDENTIFIER ::= { protocols 3 }

dynObjData      OBJECT IDENTIFIER ::= { dynObjMgmt 2 }

--********************************************************************
--              Device Group
--********************************************************************
devices         OBJECT IDENTIFIER ::= { transportation 2 }



--*********************************************************************
--              Dynamic Object Group
-- ********************************************************************


dynObjDef  OBJECT-TYPE
	SYNTAX  SEQUENCE OF DynObjEntry
	ACCESS  not-accessible
	STATUS  mandatory
	DESCRIPTION
		"A list of objects to be included in dynamic objects"
::= { dynObjMgmt 1 }

dynObjEntry  OBJECT-TYPE
	SYNTAX  DynObjEntry
	ACCESS  not-accessible
	STATUS  mandatory
	DESCRIPTION
		"A list of OBJECT IDENTIFIERs that make up a dynamic object"
	INDEX  { dynObjNumber,  dynObjIndex }
::= { dynObjDef 1 }

DynObjEntry ::= SEQUENCE {
  dynObjNumber    INTEGER (1..13),
  dynObjIndex     UByte,
	dynObjVariable  OBJECT IDENTIFIER,
  dynObjOwner     OwnerString,
  dynObjStatus    EntryStatus  }

dynObjNumber  OBJECT-TYPE
	SYNTAX  INTEGER ( 1..13)
	ACCESS  read-write
	STATUS  mandatory
	DESCRIPTION
		"The dynamic object number that this entry is to be associated with.  The
    order in which objects are transmitted for a given dynamic object number is
    based on the value of the dynObjIndex.  Lower values of dynObjIndex are
    transmitted first (for the same value of dynObjNumber).
	
		This object may not be modified if the associated dynObjStatus object is
    equal to valid(1)."
::= { dynObjEntry 2 }

dynObjIndex  OBJECT-TYPE
	SYNTAX  UByte
	ACCESS  read-only
	STATUS  mandatory
	DESCRIPTION
		"An index that uniquely identifies an entry in the dynamic object table.
    Each entry defines an object that is to be associated with a dynamic object
    number.   The dynObjIndex and dynObjNumber together determine the order in
    which objects are transmitted for the dynamic object.  The lower dynObjIndex
    numbers are transmitted before larger numbers for entries with the same
    dynObjNumber."
::= { dynObjEntry 1 }

dynObjVariable OBJECT-TYPE
	SYNTAX  OBJECT IDENTIFIER
	ACCESS  read-write
	STATUS  mandatory
	DESCRIPTION
		"The object identifier of the particular variable to be included in the
    specified dynamic object number.  Care must be taken when defining dynamic
    objects that the maximum size of all the objects included in a dynamic
    object do not exceed the maximum packet size of the communications network.
	
		This object may not be modified if the associated dynObjStatus object is
    equal to valid(1)."
::= { dynObjEntry 3 }

dynObjOwner OBJECT-TYPE
	SYNTAX  OwnerString
	ACCESS  read-write
	STATUS  mandatory
	DESCRIPTION
		"The entity that configured this entry and is therefore using the resources 
		assigned to it.
		This object may not be modified if the associated dynObjStatus object is
    equal to valid(1)."
::= { dynObjEntry 4 }

dynObjStatus OBJECT-TYPE
	SYNTAX  EntryStatus
	ACCESS  read-write
	STATUS  mandatory
	DESCRIPTION
		"The status of this dynamic object definition entry.  See description of 
		EntryStatus above for restrictions on accesses"
::= { dynObjEntry 5 }

-- END -- TMIB DEFINITIONS


--***********************************************************************
--              Dynamic Object Data
--***********************************************************************

dynObj1  OBJECT-TYPE
	SYNTAX  OCTET STRING
	ACCESS  read-write
	STATUS  mandatory
	DESCRIPTION
		"The value of this object is determined by the dynObjDef entries with 
		dynObjNumber equal to 1.  Packed Encoding Rules are utilized to encode
		the objects for transmission.  This object is intended for use with the
    Simple Transportation Management Protocol, and provides little advantage if
    used with SNMP.
		If no objects are defined for this dynamic object number, then an error of 
		noSuchName shall be returned by the agent"
::= { dynObjData 1 }

dynObj2  OBJECT-TYPE
	SYNTAX  OCTET STRING
	ACCESS  read-write
	STATUS  mandatory
	DESCRIPTION
		"The value of this object is determined by the dynObjDef entries with 
		dynObjNumber equal to 2.  Packed Encoding Rules are utilized to encode
		the objects for transmission.  This object is intended for use with the
    Simple Transportation Management Protocol, and provides little advantage if
    used with SNMP.
		If no objects are defined for this dynamic object number, then an error of 
		noSuchName shall be returned by the agent"
::= { dynObjData 2 }

dynObj3  OBJECT-TYPE
	SYNTAX  OCTET STRING
	ACCESS  read-write
	STATUS  mandatory
	DESCRIPTION
		"The value of this object is determined by the dynObjDef entries with 
		dynObjNumber equal to 3.  Packed Encoding Rules are utilized to encode
		the objects for transmission.  This object is intended for use with the
    Simple Transportation Management Protocol, and provides little advantage if
    used with SNMP.
		If no objects are defined for this dynamic object number, then an error of 
		noSuchName shall be returned by the agent"
::= { dynObjData 3 }

dynObj4  OBJECT-TYPE
	SYNTAX  OCTET STRING
	ACCESS  read-write
	STATUS  mandatory
	DESCRIPTION
		"The value of this object is determined by the dynObjDef entries with 
		dynObjNumber equal to 4.  Packed Encoding Rules are utilized to encode
		the objects for transmission.  This object is intended for use with the
    Simple Transportation Management Protocol, and provides little advantage if
    used with SNMP.
		If no objects are defined for this dynamic object number, then an error of 
		noSuchName shall be returned by the agent"
::= { dynObjData 4 }

dynObj5  OBJECT-TYPE
	SYNTAX  OCTET STRING
	ACCESS  read-write
	STATUS  mandatory
	DESCRIPTION
		"The value of this object is determined by the dynObjDef entries with 
		dynObjNumber equal to 5.  Packed Encoding Rules are utilized to encode
		the objects for transmission.  This object is intended for use with the
    Simple Transportation Management Protocol, and provides little advantage if
    used with SNMP.
		If no objects are defined for this dynamic object number, then an error of 
		noSuchName shall be returned by the agent"
::= { dynObjData 5 }

dynObj6  OBJECT-TYPE
	SYNTAX  OCTET STRING
	ACCESS  read-write
	STATUS  mandatory
	DESCRIPTION
		"The value of this object is determined by the dynObjDef entries with 
		dynObjNumber equal to 6.  Packed Encoding Rules are utilized to encode
		the objects for transmission.  This object is intended for use with the
    Simple Transportation Management Protocol, and provides little advantage if
    used with SNMP.
		If no objects are defined for this dynamic object number, then an error of 
		noSuchName shall be returned by the agent"
::= { dynObjData 6 }

dynObj7  OBJECT-TYPE
	SYNTAX  OCTET STRING
	ACCESS  read-write
	STATUS  mandatory
	DESCRIPTION
		"The value of this object is determined by the dynObjDef entries with 
		dynObjNumber equal to 7.  Packed Encoding Rules are utilized to encode
		the objects for transmission.  This object is intended for use with the
    Simple Transportation Management Protocol, and provides little advantage if
    used with SNMP.
		If no objects are defined for this dynamic object number, then an error of 
		noSuchName shall be returned by the agent"
::= { dynObjData 7 }

dynObj8  OBJECT-TYPE
	SYNTAX  OCTET STRING
	ACCESS  read-write
	STATUS  mandatory
	DESCRIPTION
		"The value of this object is determined by the dynObjDef entries with 
		dynObjNumber equal to 8.  Packed Encoding Rules are utilized to encode
		the objects for transmission.  This object is intended for use with the
    Simple Transportation Management Protocol, and provides little advantage if
    used with SNMP.
		If no objects are defined for this dynamic object number, then an error of 
		noSuchName shall be returned by the agent"
::= { dynObjData 8 }

dynObj9  OBJECT-TYPE
	SYNTAX  OCTET STRING
	ACCESS  read-write
	STATUS  mandatory
	DESCRIPTION
		"The value of this object is determined by the dynObjDef entries with 
		dynObjNumber equal to 9.  Packed Encoding Rules are utilized to encode
		the objects for transmission.  This object is intended for use with the
    Simple Transportation Management Protocol, and provides little advantage if
    used with SNMP.
		If no objects are defined for this dynamic object number, then an error of 
		noSuchName shall be returned by the agent"
::= { dynObjData 9 }

dynObj10  OBJECT-TYPE
	SYNTAX  OCTET STRING
	ACCESS  read-write
	STATUS  mandatory
	DESCRIPTION
		"The value of this object is determined by the dynObjDef entries with 
		dynObjNumber equal to 10.  Packed Encoding Rules are utilized to encode
		the objects for transmission.  This object is intended for use with the
    Simple Transportation Management Protocol, and provides little advantage if
    used with SNMP.
		If no objects are defined for this dynamic object number, then an error of 
		noSuchName shall be returned by the agent"
::= { dynObjData 10 }

dynObj11  OBJECT-TYPE
	SYNTAX  OCTET STRING
	ACCESS  read-write
	STATUS  mandatory
	DESCRIPTION
		"The value of this object is determined by the dynObjDef entries with 
		dynObjNumber equal to 11.  Packed Encoding Rules are utilized to encode
		the objects for transmission.  This object is intended for use with the
    Simple Transportation Management Protocol, and provides little advantage if
    used with SNMP.
		If no objects are defined for this dynamic object number, then an error of 
		noSuchName shall be returned by the agent"
::= { dynObjData 11 }

dynObj12  OBJECT-TYPE
	SYNTAX  OCTET STRING
	ACCESS  read-write
	STATUS  mandatory
	DESCRIPTION
		"The value of this object is determined by the dynObjDef entries with 
		dynObjNumber equal to 12.  Packed Encoding Rules are utilized to encode
		the objects for transmission.  This object is intended for use with the
    Simple Transportation Management Protocol, and provides little advantage if
    used with SNMP.
		If no objects are defined for this dynamic object number, then an error of 
		noSuchName shall be returned by the agent"
::= { dynObjData 12 }

dynObj13  OBJECT-TYPE
        SYNTAX  OCTET STRING
	ACCESS  read-write
	STATUS  mandatory
	DESCRIPTION
    "The value of this object is determined by the dynObjDef entries with 
		dynObjNumber equal to 13.  Packed Encoding Rules are utilized to encode
		the objects for transmission.  This object is intended for use with the
    Simple Transportation Management Protocol, and provides little advantage if
    used with SNMP.
		If no objects are defined for this dynamic object number, then an error of 
		noSuchName shall be returned by the agent"
::= { dynObjData 13 }

END -- TMIB DEFINITIONS
