--******************************************************************************
-- Filename:    TS32_SMI.MIB
-- Version:     0.A
-- Date:        January 1, 1998
-- Description: This MIB defines the structure of information under the internet
--              enterprises node
-- Revision:    0.A - Preliminary Release of TS 3.2 NEMA_SMI MIB formatted for
--              80 columns and no tabs
-- SMIC Compiler
-- Notes:
--              Deleted EXPORTS
--
--******************************************************************************


NEMA_SMI DEFINITIONS ::= BEGIN

-- Initial definitions for NEMA Structure of Management Information.
-- This contains only structure information, no managed objects are defined

IMPORTS
   enterprises
       FROM RFC1155-SMI;

-- EXPORTS -- EVERYTHING
-- Major groups of the NEMA_SMI
--    nema, nema.mgmt, nema.experimental, nema.private, transportation

-- NEMA has received ID 1206 from IANA
-- NEMA starts at { iso 3 6 internet private enterprises 1206 } in the global
-- naming tree.

nema                    OBJECT IDENTIFIER  ::=  { enterprises 1206 }

mgmt                    OBJECT IDENTIFIER  ::=  { nema 1 }
experimental            OBJECT IDENTIFIER  ::=  { nema 2 }
private                 OBJECT IDENTIFIER  ::=  { nema 3 }
transportation          OBJECT IDENTIFIER  ::=  { nema 4 }


-- The mgmt subtree is used for standard NEMA object definitions that span 
-- different NEMA sections.
-- The experimental subtree is used for technical committees developing objects 
-- that may become standard in the future.
-- The private subtree is used for unilaterally defined objects.  One common use is
-- for manufacturer specific or customer specific MIB definitions.
-- The transportation subtree is used by the NEMA 3 TS section to define
-- standard objects specific for the transportation industry.

END -- NEMA_SMI Definitions
