--******************************************************************************
-- Filename:    TS32bSMI.MIB
-- Version:     0.B
-- Date:        July 8, 1998
-- Description: This MIB defines the structure of information under the internet
--              enterprises node
-- Revisions:
--  1/1/98      0.A - Preliminary Release of TS 3.2 NEMA_SMI MIB formatted for
--              80 columns and no tabs
--  7/8/98      0.B - Added Copyright Notice
-- SMIC Compiler
-- Notes:
--              Deleted EXPORTS
--
--(c) Copyright 1998 by the American Association of State Highway 
--and Transportation Officials (AASHTO), the Institute of 
--Transportation Engineers (ITE), and the National Electrical 
--Manufacturers Association (NEMA).  All intellectual property rights, 
--including, but not limited to, the rights of reproduction, translation 
--and display are reserved under the laws of the United States of 
--America, the Universal Copyright Convention, the Berne Convention, 
--and the International and Pan American Copyright Conventions.  Except
--as provided, you may not copy these materials without written 
--permission from either AASHTO, ITE, or NEMA.  Use of these materials 
--does not give you any rights of ownership or claim of copyright in 
--or to these materials.
--
--To the extent and in the limited event these materials are 
--distributed by AASHTO/ITE/NEMA in the form of a Management 
--Information Base ("MIB"), AASHTO/ITE/NEMA extends the following 
--permissions:
--
--(i)  you may make and/or distribute unlimited copies (including 
--derivative works) of the MIB, including copies for commercial 
--distribution, provided that (a) each copy you make and/or distribute 
--contains this Notice and (b) each derivative work of the MIB uses 
--the same module name followed by "-", followed by your Internet 
--Assigned Number Authority (IANA)-assigned enterprise number;
--(ii)  use of the MIB is restricted in that the syntax field may be 
--modified only to reflect a more restrictive subrange or enumerated 
--values;
--(iii)  the description field may be modified but only to the extent 
--that:  (a) only those bit values or enumerated values that are 
--supported are listed; and (b) the more restrictive subrange is 
--expressed.
--
--These materials are delivered "AS IS" without any warranties as to 
--their use or performance.
--
--AASHTO/ITE/NEMA AND THEIR SUPPLIERS DO NOT WARRANT THE PERFORMANCE 
--OR RESULTS YOU MAY OBTAIN BY USING THESE MATERIALS.  AASHTO/ITE/NEMA 
--AND THEIR SUPPLIERS MAKE NO WARRANTIES, EXPRESS OR IMPLIED, AS TO 
--NONINFRINGEMENT OF THIRD PARTY RIGHTS, MERCHANTABILITY, OR FITNESS 
--FOR ANY PARTICULAR PURPOSE.  IN NO EVENT WILL AASHTO, ITE OR NEMA 
--OR THEIR SUPPLIERS BE LIABLE TO YOU OR ANY THIRD PARTY FOR ANY CLAIM 
--OR FOR ANY CONSEQUENTIAL, INCIDENTAL OR SPECIAL DAMAGES, INCLUDING 
--ANY LOST PROFITS OR LOST SAVINGS, ARISING FROM YOUR REPRODUCTION OR 
--USE OF THESE MATERIALS, EVEN IF AN AASHTO, ITE, OR NEMA 
--REPRESENTATIVE HAS BEEN ADVISED OF THE POSSIBILITY OF SUCH DAMAGES.  
--Some states or jurisdictions do not allow the exclusion or 
--limitation of incidental, consequential or special damages, or the 
--exclusion of implied warranties, so the above limitations may not 
--apply to you.
--
--Use of these materials does not constitute an endorsement or 
--affiliation by or between AASHTO, ITE, or NEMA and you, your company, 
--or your products and services.
--
--If you are unwilling to accept the foregoing restrictions, you 
--should immediately return these materials.
--
--NTCIP is a trademark of AASHTO/ITE/NEMA.
--******************************************************************************


NEMA_SMI DEFINITIONS ::= BEGIN

-- Initial definitions for NEMA Structure of Management Information.
-- This contains only structure information, no managed objects are defined

IMPORTS
   enterprises
       FROM RFC1155-SMI;

-- EXPORTS -- EVERYTHING
-- Major groups of the NEMA_SMI
--    nema, nema.mgmt, nema.experimental, nema.private, transportation

-- NEMA has received ID 1206 from IANA
-- NEMA starts at { iso 3 6 internet private enterprises 1206 } in the global
-- naming tree.

nema                    OBJECT IDENTIFIER  ::=  { enterprises 1206 }

mgmt                    OBJECT IDENTIFIER  ::=  { nema 1 }
experimental            OBJECT IDENTIFIER  ::=  { nema 2 }
private                 OBJECT IDENTIFIER  ::=  { nema 3 }
transportation          OBJECT IDENTIFIER  ::=  { nema 4 }


-- The mgmt subtree is used for standard NEMA object definitions that span 
-- different NEMA sections.
-- The experimental subtree is used for technical committees developing objects 
-- that may become standard in the future.
-- The private subtree is used for unilaterally defined objects.  One common use is
-- for manufacturer specific or customer specific MIB definitions.
-- The transportation subtree is used by the NEMA 3 TS section to define
-- standard objects specific for the transportation industry.

END -- NEMA_SMI Definitions
