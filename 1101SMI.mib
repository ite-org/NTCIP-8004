--******************************************************************************
-- Filename:    1101SMI.MIB
-- Source:		1101(SMI).MIB
-- Description: This MIB defines the structure of information under the internet
--              enterprises node
-- MIB Revision History:
-- 01/01/98     Preliminary Release of TS 3.2 NEMA_SMI MIB formatted for
--              80 columns and no tabs
-- 07/08/98     Added Copyright Notice
-- 03/09/00	    Changed filename and updated copyright years
--              Updated the MIB to Amendment  
-- 08/09/00     Modified header format and wording of copyright and MIB
--              Distribution Notice
-- 08/11/00     Changed filename for use with public domain compiler (SMIC).
--
--Copyright 1996-2000 by the American Association of State Highway and
--Transportation Officials (AASHTO), the Institute of Transportation Engineers
--(ITE), and the National Electrical Manufacturers Association (NEMA).  All
--intellectual property rights, including, but not limited to, the rights of
--reproduction in whole or in part in any form, translation into other
--languages and display are reserved by the copyright owners under the laws of
--the United States of America, the Universal Copyright Convention, the Berne
--Convention, and the International and Pan American Copyright Conventions.
--Except for the MIB, Do not copy without written permission of either AASHTO,
--ITE, or NEMA.
--
--                     Joint NEMA, AASHTO, and ITE
--                  NTCIP Management Information Base
--                        DISTRIBUTION NOTICE
--
--To the extent and in the limited event these materials are distributed by
--AASHTO/ITE/NEMA in the form of a Management Information Base ("MIB"), 
--AASHTO/ITE/NEMA extends the following permissions:
--
-- (i) you may make and/or distribute unlimited copies (including derivative
--works) of the MIB, including copies for commercial distribution, provided
--that (a) each copy you make and/or distribute contains this Notice and (b)
--each derivative work of the MIB uses the same module name followed by "-",
--followed by your Internet Assigned Number Authority (IANA)-assigned 
--enterprise number;
--(ii) use of the MIB is restricted in that the syntax field may be modified
--only to reflect a more restrictive sub-range or enumerated values;
--(iii) the description field may be modified but only to the extent that:
--(a) only those bit values or enumerated values that are supported are
--listed; and (b) the more restrictive subrange is expressed.
--
--These materials are delivered "AS IS" without any warranties as to their use
--or performance.
--
--AASHTO/ITE/NEMA AND THEIR SUPPLIERS DO NOT WARRANT THE PERFORMANCE OR
--RESULTS YOU MAY OBTAIN BY USING THESE MATERIALS.  AASHTO/ITE/NEMA AND THEIR
--SUPPLIERS MAKE NO WARRANTIES, EXPRESS OR IMPLIED, AS TO NONINFRINGEMENT OF
--THIRD PARTY RIGHTS, MERCHANTABILITY, OR FITNESS FOR ANY PARTICULAR PURPOSE.
--IN NO EVENT WILL AASHTO, ITE OR NEMA OR THEIR SUPPLIERS BE LIABLE TO YOU OR
--ANY THIRD PARTY FOR ANY CLAIM OR FOR ANY CONSEQUENTIAL, INCIDENTAL OR
--SPECIAL DAMAGES, INCLUDING ANY LOST PROFITS OR LOST SAVINGS, ARISING FROM
--YOUR REPRODUCTION OR USE OF THESE MATERIALS, EVEN IF AN AASHTO, ITE, OR NEMA
--REPRESENTATIVE HAS BEEN ADVISED OF THE POSSIBILITY OF SUCH DAMAGES.  Some
--states or jurisdictions do not allow the exclusion or limitation of
--incidental, consequential or special damages, or the exclusion of implied
--warranties, so the above limitations may not apply to you.
--
--Use of these materials does not constitute an endorsement or affiliation by
--or between AASHTO, ITE, or NEMA and you, your company, or your products and
--services.
--
--NTCIP is a trademark of AASHTO/ITE/NEMA.
--******************************************************************************


NEMA_SMI DEFINITIONS ::= BEGIN

-- Initial definitions for NEMA Structure of Management Information.
-- This contains only structure information, no managed objects are defined

IMPORTS
   enterprises
       FROM RFC1155-SMI;

-- EXPORTS -- EVERYTHING
-- Major groups of the NEMA_SMI
--    nema, nema.mgmt, nema.experimental, nema.private, transportation

-- NEMA has received ID 1206 from IANA
-- NEMA starts at { iso org dod internet private enterprises 1206 } in the global
-- naming tree.

nema                    OBJECT IDENTIFIER  ::=  { enterprises 1206 }

nemaMgmt                OBJECT IDENTIFIER  ::=  { nema 1 }
nemaExperimental        OBJECT IDENTIFIER  ::=  { nema 2 }
nemaPrivate             OBJECT IDENTIFIER  ::=  { nema 3 }
transportation          OBJECT IDENTIFIER  ::=  { nema 4 }


-- The mgmt subtree is used for standard NEMA object definitions that span 
-- different NEMA sections.
-- The experimental subtree is used for technical committees developing objects 
-- that may become standard in the future.
-- The private subtree is used for unilaterally defined objects.  One common use is
-- for manufacturer specific or customer specific MIB definitions.
-- The transportation subtree is used by the NEMA 3 TS section to define
-- standard objects specific for the transportation industry.

END -- NEMA_SMI Definitions
